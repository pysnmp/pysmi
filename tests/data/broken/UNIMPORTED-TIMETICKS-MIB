-- Minimal reproducer for a workaround in the code generators.
--
-- Seen in IETF MIBs; DSA-MIB is the module named in the source comment.
--
-- The module uses TimeTicks without naming it in IMPORTS. That is invalid per
-- RFC 2578 Section 3.2, but the generators carry TimeTicks in their constImports
-- set so the module still compiles. Deleting it from constImports breaks this
-- module -- which is the point of keeping the reproducer.

UNIMPORTED-TIMETICKS-MIB DEFINITIONS ::= BEGIN

IMPORTS
    OBJECT-TYPE
        FROM SNMPv2-SMI;

brokenObject OBJECT-TYPE
    SYNTAX      TimeTicks
    MAX-ACCESS  read-only
    STATUS      current
    DESCRIPTION
        "An object whose syntax is never imported."
    ::= { 1 3 1 }

END
