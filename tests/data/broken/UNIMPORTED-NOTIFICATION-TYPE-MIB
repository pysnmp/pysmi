-- Minimal reproducer for a workaround in the code generators.
--
-- Seen in vendor MIBs; A3COM-HUAWEI-DHCPSNOOP-MIB is the module named in the
-- source comment.
--
-- The module invokes the NOTIFICATION-TYPE macro without naming it in IMPORTS.
-- That is invalid per RFC 2578 Section 3.2, but the generators carry
-- NOTIFICATION-TYPE in their constImports set so the module still compiles.
-- Deleting it from constImports breaks this module -- which is the point of
-- keeping the reproducer.

UNIMPORTED-NOTIFICATION-TYPE-MIB DEFINITIONS ::= BEGIN

IMPORTS
    OBJECT-TYPE, Integer32
        FROM SNMPv2-SMI;

brokenObject OBJECT-TYPE
    SYNTAX      Integer32
    MAX-ACCESS  read-only
    STATUS      current
    DESCRIPTION
        "An object to hang the notification off."
    ::= { 1 3 1 }

brokenNotification NOTIFICATION-TYPE
    OBJECTS     { brokenObject }
    STATUS      current
    DESCRIPTION
        "A notification whose macro is never imported."
    ::= { 1 3 2 }

END
